FME workspace UpdatePortal_Hostname.fmw

Parameters:
- DestDataset_XLSXW = $(FME_MF_DIR)SSLConversionResults_cent_stav_west_stg.xlsx   # Destination Microsoft Excel File
- SourceDataset_XLSXR_3 = $(FME_MF_DIR)PortalMapServiceUpdates.xlsx   # Source Microsoft Excel File(s)

Readers:
- XLSXR_1: XLSXR from $(SourceDataset_XLSXR_3)

Writers:
- XLSXW_1: XLSXW to $(DestDataset_XLSXW)

AttributeRemover
    REMOVE_ATTRS = Password,_headers{0}.name,_headers{0}.value,Username,tokenResponse,_http_status_code
    -> Get_All_Portal_Users
Get_All_Portal_Users: HttpCaller_Pager
    PORTAL_URL = @Value(Portal URL)
    TOKEN = @Value(token)
    -> Get_Items_For_User
Get_Items_For_User
    PORTAL_URL = @Value(Portal URL)
    USERNAME = @Value(username)
    TOKEN = @Value(token)
    Edit_URLs_With_URL_Attribute -> Create_OldURL
    Edit_URLs_With_No_URL_Attribute -> Type_of_Item_Filter
    Edit_URLs_With_No_URL_Attribute -> Restrict_to_single_Item_ID_2 [off]
Create_OldURL: AttributeCreator
    ATTR_TABLE = SET_TO oldURL = @Value(url)
    -> Check_for_Old_Hostname
    -> Restrict_to_single_Item_ID [off]
    -> HTTP_Calls_for_Data_No_Folder
AttributeRemover_2
    REMOVE_ATTRS = ItemEditURL,currentFolder.id,id,item,itemType,_http_status_code,description,type,token
    LIST_ATTRS = _headers{} _headers{}.name _headers{}.value
    -> AttributeCreator_4
AttributeCreator_4
    ATTR_TABLE = SET_TO SheetName = MapServices
    -> Sheet1 (writer XLSXW_1)
Restrict_to_single_Item_ID: Tester [off]
    TEST_CLAUSE = TEST @Value(id) = 95ebe5c373de4258b3a99f22c1986964
    BOOL_OP = OR
    TEST_MODE = Automatic
    TEST_DESCRIPTION = ""
    PASSED -> HTTP_Calls_for_Data_No_Folder [off]
Restrict_to_single_Item_ID_2: Tester [off]
    TEST_CLAUSE = TEST @Value(id) = 95ebe5c373de4258b3a99f22c1986964
    BOOL_OP = OR
    TEST_MODE = Automatic
    TEST_DESCRIPTION = ""
    PASSED -> Type_of_Item_Filter [off]
Type_of_Item_Filter: TestFilter
    DEFAULT_VALUE = <UNFILTERED>
    TEST_LIST = BOOL_OP,OR,COMPOSITE_TEST,<Unused>,TEST_CLAUSE,"TEST @Value(type) = Web Map",Web Maps,BOOL_OP,OR,COMPOSITE_TEST,<Unused>,TEST_CLAUSE,"TEST @Value(type) = CityEngine Web Scene",CityEngine Web Scenes,BOOL_OP,OR,COMPOSITE_TEST,<Unused>,TEST_CLAUSE,"TEST @Value(type) = Web Scene",Web Scenes,BOOL_OP,OR,COMPOSITE_TEST,<Unused>,TEST_CLAUSE,"TEST @Value(type) = Pro Map",Pro Maps,BOOL_OP,OR,COMPOSITE_TEST,<Unused>,TEST_CLAUSE,"TEST @Value(type) = Feature Service",Feature Services,BOOL_OP,OR,COMPOSITE_TEST,<Unused>,TEST_CLAUSE,"TEST @Value(type) = Map Service",Map Services,BOOL_OP,OR,COMPOSITE_TEST,<Unused>,TEST_CLAUSE,"TEST @Value(type) = Stream Service",Stream Services,BOOL_OP,OR,COMPOSITE_TEST,<Unused>,TEST_CLAUSE,"TEST @Value(type) = Image Service",Image Services,BOOL_OP,OR,COMPOSITE_TEST,<Unused>,TEST_CLAUSE,"TEST @Value(type) = KML",KMLs,BOOL_OP,OR,COMPOSITE_TEST,<Unused>,TEST_CLAUSE,"TEST @Value(type) = WMS",WMSs,BOOL_OP,OR,COMPOSITE_TEST,<Unused>,TEST_CLAUSE,"TEST @Value(type) = Feature Collection",Feature Collections,BOOL_OP,OR,COMPOSITE_TEST,<Unused>,TEST_CLAUSE,"TEST @Value(type) = Feature Collection Template",Feature Collection Templates,BOOL_OP,OR,COMPOSITE_TEST,<Unused>,TEST_CLAUSE,"TEST @Value(type) = Geodata Service",Geodata Services,BOOL_OP,OR,COMPOSITE_TEST,<Unused>,TEST_CLAUSE,"TEST @Value(type) = Globe Service",Globe Services,BOOL_OP,OR,COMPOSITE_TEST,<Unused>,TEST_CLAUSE,"TEST @Value(type) = Web Mapping Application",Web Mapping Applications,BOOL_OP,OR,COMPOSITE_TEST,<Unused>,TEST_CLAUSE,"TEST @Value(type) = Mobile Application",Mobile Applications,BOOL_OP,OR,COMPOSITE_TEST,<Unused>,TEST_CLAUSE,"TEST @Value(type) = Code Attachment",Code Attachments,BOOL_OP,OR,COMPOSITE_TEST,<Unused>,TEST_CLAUSE,"TEST @Value(type) = Operations Dashboard Add In",Ops Dashboard Add Ins,BOOL_OP,OR,COMPOSITE_TEST,<Unused>,TEST_CLAUSE,"TEST @Value(type) = Operation View",Operation Views,BOOL_OP,OR,COMPOSITE_TEST,<Unused>,TEST_CLAUSE,"TEST @Value(type) = Operations Dashboard Extension",Ops Dashboard Extensions,BOOL_OP,OR,COMPOSITE_TEST,<Unused>,TEST_CLAUSE,"TEST @Value(type) = Native Application",Native Applications,BOOL_OP,OR,COMPOSITE_TEST,<Unused>,TEST_CLAUSE,"TEST @Value(type) = Native Application Template",Native Application Templates,BOOL_OP,OR,COMPOSITE_TEST,<Unused>,TEST_CLAUSE,"TEST @Value(type) = Native Application Installer",Native App Installers,BOOL_OP,OR,COMPOSITE_TEST,<Unused>,TEST_CLAUSE,"TEST @Value(type) = Geometry Service",Geometry Services,BOOL_OP,OR,COMPOSITE_TEST,<Unused>,TEST_CLAUSE,"TEST @Value(type) = Geocoding Service",Geocoding Services,BOOL_OP,OR,COMPOSITE_TEST,<Unused>,TEST_CLAUSE,"TEST @Value(type) = Network Analysis Service",Network Analysis Services,BOOL_OP,OR,COMPOSITE_TEST,<Unused>,TEST_CLAUSE,"TEST @Value(type) = Geoprocessing Service",Geoprocessing Services,BOOL_OP,OR,COMPOSITE_TEST,<Unused>,TEST_CLAUSE,"TEST @Value(type) = Workflow Manager Service",Wrokflow Manager Services
    Web Maps -> HTTP_Calls_for_Data_No_Folder
HTTP_Calls_for_Data_No_Folder: HTTPCaller
    FOLLOW_REDIRECTS = Yes
    ERROR_ATTR = _error
    TRANSFER_TIMEOUT_LENGTH = 90
    TARGET_URL = @Value(Portal URL)/sharing/rest/content/items/@Value(id)/data
    STATUS_CODE_ATTR = _http_status_code
    USE_COOKIES = No
    ADDITIONAL_URL_PARAMETERS = f;pjson token;@Value(token)
    VERIFY_SSL_CERTIFICATES = No
    HTTP_METHOD = GET
    FILE_TYPE = <Auto Detect from HTTP Headers>
    TARGET_ATTR_ENCODING = auto-detect
    RESPONSE_HEADER_LIST_ATTR = _headers
    TARGET_ATTR = ItemDataResponse
    SAVE_FILE = Attribute
    CONNECTION_TIMEOUT_LENGTH = 60
    -> Check_if_Item_has_Data
Check_if_Item_has_Data: Tester
    TEST_CLAUSE = TEST ItemDataResponse NOT_ATTRIBUTE_VALUE_NULL ""
    BOOL_OP = OR
    TEST_MODE = Automatic
    TEST_DESCRIPTION = ""
    PASSED -> Check_for_Old_Hostname_for_Item_Data
Note: Check_for_Old_Hostname_for_Item_Data [Tester] / Test Description: "" / TEST @Value(ItemDataResponse) CONTAINS @Value(Old Server) / Condition: OR
Check_for_Old_Hostname_for_Item_Data: Tester
    TEST_CLAUSE = TEST @Value(ItemDataResponse) CONTAINS @Value(Old Server)
    BOOL_OP = OR
    TEST_MODE = Automatic
    TEST_DESCRIPTION = ""
    PASSED -> Create_New_Attr_for_HTTPS_conversion
Create_New_Attr_for_HTTPS_conversion: AttributeCreator
    ATTR_TABLE = SET_TO newItemDataResponse = @Value(ItemDataResponse)
    -> Replace_Hostname_with_New_for_Item_Data
Note: Replace_Hostname_with_New_for_Item_Data [StringReplacer] / Attributes: newItemDataResponse / Text to Find: @Value(Old Server) / Replacement Text: @Value(New Server) / Use Regular Expressions: No / Case Sensitive: No / If Attribute Value Does Not Match Text: / Set Attribute Value To:<Do Nothing>
Replace_Hostname_with_New_for_Item_Data: StringReplacer
    REPLACE_TEXT = @Value(New Server)
    NO_MATCH = _FME_NO_OP_
    CASE = NO
    FIND_TEXT = @Value(Old Server)
    REGEXP = NO
    SRC_ATTRS = newItemDataResponse
    -> New_URL_NOT_NULL
New_URL_NOT_NULL: Tester
    TEST_CLAUSE = TEST newItemDataResponse NOT_ATTRIBUTE_VALUE_NULL ""
    BOOL_OP = OR
    TEST_MODE = Automatic
    TEST_DESCRIPTION = ""
    PASSED -> Encode_URL_Data
Encode_URL_Data: TextEncoder
    ENCODING_TYPE = URL (Percent Encoding)
    DEST_ATTR = EncodedDataResponse
    STRING_TO_ENCODE = @Value(newItemDataResponse)
    -> Test_for_Folder
Note: Passed = no Folder / Failed = Folder
Test_for_Folder: Tester
    TEST_CLAUSE = TEST currentFolder.id ATTRIBUTE_VALUE_NULL ""
    BOOL_OP = OR
    TEST_MODE = Automatic
    TEST_DESCRIPTION = ""
    PASSED -> AttributeCreator_2
    FAILED -> AttributeCreator_3
AttributeCreator_2
    ATTR_TABLE = SET_TO UpdateDataURL = @Value(Portal URL)/sharing/rest/content/users/@Value(username)/items/@Value(id)/update
    -> Update_Data_Item
AttributeCreator_3
    ATTR_TABLE = SET_TO UpdateDataURL = @Value(Portal URL)/sharing/rest/content/users/@Value(username)/@Value(currentFolder.id)/items/@Value(id)/update
    -> Update_Data_Item
AttributeCreator_5
    ATTR_TABLE = SET_TO SheetName = Other
    -> Sheet1 (writer XLSXW_1)
Sheet1 (writer XLSXW_1) [off]
    attributes: newItemDataResponse auto(20), currentFolder.title string(20), Portal URL string(20), Portal Name string(20), username string(20), title string(20), id auto(20), url string(20), itemType auto(20), description auto(20), type auto(20), ItemDataResponse auto(20), oldURL auto(20)

Bookmark: Token Generation
Sheet1 (reader XLSXR_1)
    attributes: Portal URL char(43), Portal Name string, Username char(12), Password char(11), Old Server char(15), New Server char(15)
    -> GenerateToken
GenerateToken: HTTPCaller
    FOLLOW_REDIRECTS = Yes
    ERROR_ATTR = _error
    TRANSFER_TIMEOUT_LENGTH = 90
    TARGET_URL = @Value(Portal URL)/sharing/generatetoken
    MULTIPARTS = username StringUpload SOURCE_EXPRESSION;@Value(Username);MIME_TYPE;text/plain;FME_CONTROLLER_QUERY_FILE;transformers\dependencies\http\StringUpload.fme password StringUpload SOURCE_EXPRESSION;@Value(Password);MIME_TYPE;text/plain;FME_CONTROLLER_QUERY_FILE;transformers\dependencies\http\StringUpload.fme ip StringUpload SOURCE_EXPRESSION;;MIME_TYPE;text/plain;FME_CONTROLLER_QUERY_FILE;transformers\dependencies\http\StringUpload.fme client StringUpload SOURCE_EXPRESSION;referer;MIME_TYPE;text/plain;FME_CONTROLLER_QUERY_FILE;transformers\dependencies\http\StringUpload.fme expiration StringUpload SOURCE_EXPRESSION;20160;MIME_TYPE;text/plain;FME_CONTROLLER_QUERY_FILE;transformers\dependencies\http\StringUpload.fme f StringUpload SOURCE_EXPRESSION;json;MIME_TYPE;text/plain;FME_CONTROLLER_QUERY_FILE;transformers\dependencies\http\StringUpload.fme referer StringUpload SOURCE_EXPRESSION;@Value(Portal URL);MIME_TYPE;text/plain;FME_CONTROLLER_QUERY_FILE;transformers\dependencies\http\StringUpload.fme
    STATUS_CODE_ATTR = _http_status_code
    USE_COOKIES = No
    VERIFY_SSL_CERTIFICATES = No
    HTTP_METHOD = POST
    TARGET_ATTR_ENCODING = auto-detect
    UPLOAD_TYPE = Multipart / Form Data
    RESPONSE_HEADER_LIST_ATTR = _headers
    TARGET_ATTR = tokenResponse
    SAVE_FILE = Attribute
    CONNECTION_TIMEOUT_LENGTH = 60
    -> Expose_Token
Expose_Token: JSONFlattener
    RECURSIVE = Yes
    NEW_ATTRIBUTES = token
    JSON_ATTR = tokenResponse
    -> AttributeRemover

Bookmark: HTTPS REplacement
Note: Remove_Existing_HTTPS
Note: Check_for_Old_Hostname [Tester] / Test Description: "" / TEST @Value(url) CONTAINS @Value(Old Server) / Condition: OR
Check_for_Old_Hostname: Tester
    TEST_CLAUSE = TEST @Value(url) CONTAINS @Value(Old Server)
    BOOL_OP = OR
    TEST_MODE = Automatic
    TEST_DESCRIPTION = ""
    PASSED -> Replace_Hostname_with_New
Note: Replace_Hostname_with_New [StringReplacer] / Attributes: url / Text to Find: @Value(Old Server) / Replacement Text: @Value(New Server) / Use Regular Expressions: No / Case Sensitive: No / If Attribute Value Does Not Match Text: / Set Attribute Value To:<Do Nothing>
Replace_Hostname_with_New: StringReplacer
    REPLACE_TEXT = @Value(New Server)
    NO_MATCH = _FME_NO_OP_
    CASE = NO
    FIND_TEXT = @Value(Old Server)
    REGEXP = NO
    SRC_ATTRS = url
    -> Update_URLs

Bookmark: Data Update
Note: THIS IS WHAT UPDATES
Update_URLs: HTTPCaller
    FOLLOW_REDIRECTS = Yes
    ERROR_ATTR = _error
    TRANSFER_TIMEOUT_LENGTH = 90
    TARGET_URL = @Value(ItemEditURL)
    MULTIPARTS = url StringUpload SOURCE_EXPRESSION;@Value(url);MIME_TYPE;text/plain;FME_CONTROLLER_QUERY_FILE;transformers\dependencies\http\StringUpload.fme token StringUpload SOURCE_EXPRESSION;@Value(token);MIME_TYPE;text/plain;FME_CONTROLLER_QUERY_FILE;transformers\dependencies\http\StringUpload.fme f StringUpload SOURCE_EXPRESSION;pjson;MIME_TYPE;text/plain;FME_CONTROLLER_QUERY_FILE;transformers\dependencies\http\StringUpload.fme
    STATUS_CODE_ATTR = _http_status_code
    USE_COOKIES = No
    VERIFY_SSL_CERTIFICATES = No
    HTTP_METHOD = POST
    FILE_TYPE = <Auto Detect from HTTP Headers>
    TARGET_ATTR_ENCODING = auto-detect
    UPLOAD_TYPE = Multipart / Form Data
    RESPONSE_HEADER_LIST_ATTR = _headers
    TARGET_ATTR = ItemEditStatus
    SAVE_FILE = Attribute
    CONNECTION_TIMEOUT_LENGTH = 60
    -> AttributeRemover_2
Note: THIS UPDATES DATA
Update_Data_Item: HTTPCaller
    FOLLOW_REDIRECTS = Yes
    ERROR_ATTR = _error
    TRANSFER_TIMEOUT_LENGTH = 90
    TARGET_URL = @Value(UpdateDataURL)
    MULTIPARTS = f StringUpload SOURCE_EXPRESSION;json;MIME_TYPE;text/plain;FME_CONTROLLER_QUERY_FILE;transformers\dependencies\http\StringUpload.fme token StringUpload SOURCE_EXPRESSION;@Value(token);MIME_TYPE;text/plain;FME_CONTROLLER_QUERY_FILE;transformers\dependencies\http\StringUpload.fme text StringUpload SOURCE_EXPRESSION;@Value(newItemDataResponse);MIME_TYPE;text/plain;FME_CONTROLLER_QUERY_FILE;transformers\dependencies\http\StringUpload.fme
    STATUS_CODE_ATTR = _http_status_code
    USE_COOKIES = No
    VERIFY_SSL_CERTIFICATES = No
    HTTP_METHOD = POST
    FILE_TYPE = <Auto Detect from HTTP Headers>
    TARGET_ATTR_ENCODING = auto-detect
    UPLOAD_TYPE = Multipart / Form Data
    RESPONSE_HEADER_LIST_ATTR = _headers
    TARGET_ATTR = UpdateItemDataResponse
    SAVE_FILE = Attribute
    CONNECTION_TIMEOUT_LENGTH = 60
    -> AttributeCreator_5

FME custom transformer HttpCaller_Pager

Parameters:
- PORTAL_URL = @Value(Portal URL)   # Portal URL
- TOKEN = @Value(token)   # token

Input (input)
    -> Create_Loop_Attributes
Create_Loop_Attributes: AttributeCreator
    ATTR_TABLE:
      SET_TO fetchStart = 1
      SET_TO numRecordsToFetch = 100
    -> Get_Portal_Users
Loop (input)
    -> Get_Portal_Users
Note: Pass information to Loop Iterator
Get_Portal_Users: HTTPCaller
    FOLLOW_REDIRECTS = Yes
    ERROR_ATTR = _error
    TRANSFER_TIMEOUT_LENGTH = 90
    TARGET_URL = @Value(Portal URL)/sharing/portals/0123456789ABCDEF/users
    STATUS_CODE_ATTR = _http_status_code
    USE_COOKIES = No
    ADDITIONAL_URL_PARAMETERS = f;pjson token;@Value(token) num;@Value(numRecordsToFetch) start;@Value(fetchStart)
    VERIFY_SSL_CERTIFICATES = No
    HTTP_METHOD = GET
    TARGET_ATTR_ENCODING = auto-detect
    RESPONSE_HEADER_LIST_ATTR = _headers
    TARGET_ATTR = PortalUsers
    SAVE_FILE = Attribute
    CONNECTION_TIMEOUT_LENGTH = 60
    -> Clear_List_for_Loop
Clear_List_for_Loop: AttributeRemover
    LIST_ATTRS = _headers{}.name _headers{}.value users{} users{}.username
    -> Convert_JSON_to_List
Note: Pass the information to the list creator
Convert_JSON_to_List: JSONFlattener
    RECURSIVE = Yes
    NEW_ATTRIBUTES = nextStart users{}.username
    JSON_DOCUMENT = @Value(PortalUsers)
    ERROR_LIST_ATTR = _json_error
    -> Convert_List_to_Rows
    -> Iterate_Start_Value
Iterate_Start_Value: ExpressionEvaluator
    ATTRLIST = fetchStart
    ACTION = Overwrite Existing Attributes
    EXPRESSION = @Evaluate(@Value(nextStart))
    -> Test_for_-1_Result
Test_for_-1_Result: Tester
    TEST_CLAUSE = TEST @Value(nextStart) != -1
    BOOL_OP = OR
    TEST_MODE = Automatic
    TEST_DESCRIPTION = ""
    PASSED -> Loop (output)
Note: Page through the list of users pulling 100 per call / This is a limitation of the API from ESRI
Loop (output)
Convert_List_to_Rows: ListExploder
    ATTR_CONFLICT_RES = Use Original
    ATTR_ACCUM_MODE = Merge Incoming List
    INDEX_ATTR = _usersIndex
    LIST_ATTR = users{}
    ELEMENTS -> Remove_Extra_Attributes
Remove_Extra_Attributes: AttributeRemover
    REMOVE_ATTRS = fetchStart,_usersIndex,portalToken,_http_status_code,_result,numRecordsToFetch,PortalUsers,nextStart
    LIST_ATTRS = _headers{} _headers{}.name _headers{}.value
    -> Output (output)
Output (output)

FME custom transformer Get_Items_For_User

Parameters:
- PORTAL_URL = @Value(Portal URL)   # Portal URL
- TOKEN = @Value(token)   # token
- USERNAME = @Value(username)   # username

Note: The Input Expects a Portal URL, Token, and list of UserNames for that portal
Input (input)
    -> REST_Call_for_User_Items
Note: Get A JSON Object reflecting all items and folders in a user
REST_Call_for_User_Items: HTTPCaller
    FOLLOW_REDIRECTS = Yes
    ERROR_ATTR = _error
    TRANSFER_TIMEOUT_LENGTH = 90
    TARGET_URL = @Value(Portal URL)/sharing/content/users/@Value(username)
    STATUS_CODE_ATTR = _http_status_code
    USE_COOKIES = No
    ADDITIONAL_URL_PARAMETERS = token;@Value(token) f;pjson
    VERIFY_SSL_CERTIFICATES = No
    HTTP_METHOD = GET
    FILE_TYPE = <Auto Detect from HTTP Headers>
    TARGET_ATTR_ENCODING = auto-detect
    RESPONSE_HEADER_LIST_ATTR = _headers
    TARGET_ATTR = userItemResponse
    SAVE_FILE = Attribute
    CONNECTION_TIMEOUT_LENGTH = 60
    -> JSON_FOR_ITEMS
Note: Expose the Items and Folders lists as objects
JSON_FOR_ITEMS: JSONFlattener
    RECURSIVE = Yes
    NEW_ATTRIBUTES = total items{}.title items{}.id folders{}.title folders{}.id items{}.item items{}.url items{}.itemType items{}.description items{}.type
    JSON_DOCUMENT = @Value(userItemResponse)
    ERROR_LIST_ATTR = _json_error
    -> Rename_Item_Count
Rename_Item_Count: AttributeRenamer
    ATTR_TABLE = RENAME_SET_DEFAULT total > UsersItemCount
    -> Test_For_Count_Over_0
    -> AttributeRemover
Note: Only Process Users that Have Items
Test_For_Count_Over_0: Tester
    TEST_CLAUSE = TEST @Value(UsersItemCount) > 0
    BOOL_OP = OR
    TEST_MODE = Automatic
    TEST_DESCRIPTION = ""
    PASSED -> ItemListExploder
Note: Convert the List Of Items Into Features
ItemListExploder: ListExploder
    ATTR_CONFLICT_RES = Use Incoming List
    ATTR_ACCUM_MODE = Merge Incoming List
    INDEX_ATTR = _element_index
    LIST_ATTR = items{}
    ELEMENTS -> AttributeRemover_3
    ELEMENTS -> Tester
Note: Remove Extra Attibutes before returning
AttributeRemover_3
    REMOVE_ATTRS = UsersItemCount,_element_index,_headers{0}.name,_headers{0}.value,userItemResponse,_http_status_code,folders{0}.title,folders{0}.id
    LIST_ATTRS = _headers{} _headers{}.name _headers{}.value folders{} folders{}.id folders{}.title
    -> AttributeCreator
Note: Add Folder Attributes in So Merge is Seemless / assign null instead of missing attribute
AttributeCreator
    ATTR_TABLE:
      SET_TO currentFolder.title = FME_NULL_VALUE
      SET_TO currentFolder.id = FME_NULL_VALUE
    -> Create_Non_Folder_Edit_URL
Note: Create the URL to edit the item with no folder
Create_Non_Folder_Edit_URL: AttributeCreator
    ATTR_TABLE = SET_TO ItemEditURL = @Value(Portal URL)/sharing/rest/content/users/@Value(username)/items/@Value(id)/update
    -> Type_of_Item_Filter
Note: Remove Items List from Folder Processing to prevent / duplication of users root level items for each folder
AttributeRemover
    LIST_ATTRS = items{} items{}.id items{}.title
    -> FolderListExploder
Note: For Each User Expand Their Folders
FolderListExploder: ListExploder
    ATTR_CONFLICT_RES = Use Incoming List
    ATTR_ACCUM_MODE = Merge Incoming List
    INDEX_ATTR = folderListIndex
    LIST_ATTR = folders{}
    ELEMENTS -> Rest_Call_For_Folder_Items
Note: Get List of Items In Each Folder For Each User
Rest_Call_For_Folder_Items: HTTPCaller
    FOLLOW_REDIRECTS = Yes
    ERROR_ATTR = _error
    TRANSFER_TIMEOUT_LENGTH = 90
    TARGET_URL = @Value(Portal URL)/sharing/content/users/@Value(username)/@Value(id)
    STATUS_CODE_ATTR = _http_status_code
    USE_COOKIES = No
    ADDITIONAL_URL_PARAMETERS = token;@Value(token) f;pjson
    VERIFY_SSL_CERTIFICATES = No
    HTTP_METHOD = GET
    FILE_TYPE = <Auto Detect from HTTP Headers>
    TARGET_ATTR_ENCODING = auto-detect
    RESPONSE_HEADER_LIST_ATTR = _headers
    TARGET_ATTR = JSONFolderResponse
    SAVE_FILE = Attribute
    CONNECTION_TIMEOUT_LENGTH = 60
    -> JSON_FOR_FOLDER_ITEMS
Note: Read the JSON into objects for the folder items
JSON_FOR_FOLDER_ITEMS: JSONFlattener
    RECURSIVE = Yes
    NEW_ATTRIBUTES = items{}.id items{}.item currentFolder.title currentFolder.id items{}.itemType items{}.description items{}.url items{}.title items{}.type
    JSON_DOCUMENT = @Value(JSONFolderResponse)
    ERROR_LIST_ATTR = _json_error
    -> ListExploder
Note: Convert the list of folder items into features
ListExploder
    ATTR_CONFLICT_RES = Use Incoming List
    ATTR_ACCUM_MODE = Merge Incoming List
    INDEX_ATTR = _element_index
    LIST_ATTR = items{}
    ELEMENTS -> AttributeRemover_2
    ELEMENTS -> Tester
Note: Remove Extra Attibutes before returning
AttributeRemover_2
    REMOVE_ATTRS = UsersItemCount,_element_index,_headers{0}.name,_headers{0}.value,folderListIndex,userItemResponse,_http_status_code,JSONFolderResponse
    LIST_ATTRS = _headers{} _headers{}.name _headers{}.value
    -> Create_Folder_Edit_URL
Note: Create the URL to edit the item with folder
Create_Folder_Edit_URL: AttributeCreator
    ATTR_TABLE = SET_TO ItemEditURL = @Value(Portal URL)/sharing/rest/content/users/@Value(username)/@Value(currentFolder.id)/items/@Value(id)/update
    -> Type_of_Item_Filter
Type_of_Item_Filter: TestFilter
    DEFAULT_VALUE = <UNFILTERED>
    TEST_LIST = BOOL_OP,OR,COMPOSITE_TEST,<Unused>,TEST_CLAUSE,"TEST @Value(type) = Web Map",Web Maps,BOOL_OP,OR,COMPOSITE_TEST,<Unused>,TEST_CLAUSE,"TEST @Value(type) = CityEngine Web Scene",CityEngine Web Scenes,BOOL_OP,OR,COMPOSITE_TEST,<Unused>,TEST_CLAUSE,"TEST @Value(type) = Web Scene",Web Scenes,BOOL_OP,OR,COMPOSITE_TEST,<Unused>,TEST_CLAUSE,"TEST @Value(type) = Pro Map",Pro Maps,BOOL_OP,OR,COMPOSITE_TEST,<Unused>,TEST_CLAUSE,"TEST @Value(type) = Feature Service",Feature Services,BOOL_OP,OR,COMPOSITE_TEST,<Unused>,TEST_CLAUSE,"TEST @Value(type) = Map Service",Map Services,BOOL_OP,OR,COMPOSITE_TEST,<Unused>,TEST_CLAUSE,"TEST @Value(type) = Image Service",Image Services,BOOL_OP,OR,COMPOSITE_TEST,<Unused>,TEST_CLAUSE,"TEST @Value(type) = KML",KMLs,BOOL_OP,OR,COMPOSITE_TEST,<Unused>,TEST_CLAUSE,"TEST @Value(type) = WMS",WMSs,BOOL_OP,OR,COMPOSITE_TEST,<Unused>,TEST_CLAUSE,"TEST @Value(type) = Feature Collection",Feature Collections,BOOL_OP,OR,COMPOSITE_TEST,<Unused>,TEST_CLAUSE,"TEST @Value(type) = Feature Collection Template",Feature Collection Templates,BOOL_OP,OR,COMPOSITE_TEST,<Unused>,TEST_CLAUSE,"TEST @Value(type) = Geodata Service",Geodata Services,BOOL_OP,OR,COMPOSITE_TEST,<Unused>,TEST_CLAUSE,"TEST @Value(type) = Globe Service",Globe Services,BOOL_OP,OR,COMPOSITE_TEST,<Unused>,TEST_CLAUSE,"TEST @Value(type) = Web Mapping Application",Web Mapping Applications,BOOL_OP,OR,COMPOSITE_TEST,<Unused>,TEST_CLAUSE,"TEST @Value(type) = Mobile Application",Mobile Applications,BOOL_OP,OR,COMPOSITE_TEST,<Unused>,TEST_CLAUSE,"TEST @Value(type) = Code Attachment",Code Attachments,BOOL_OP,OR,COMPOSITE_TEST,<Unused>,TEST_CLAUSE,"TEST @Value(type) = Operations Dashboard Add In",Ops Dashboard Add Ins,BOOL_OP,OR,COMPOSITE_TEST,<Unused>,TEST_CLAUSE,"TEST @Value(type) = Operation View",Operation Views,BOOL_OP,OR,COMPOSITE_TEST,<Unused>,TEST_CLAUSE,"TEST @Value(type) = Operations Dashboard Extension",Ops Dashboard Extensions,BOOL_OP,OR,COMPOSITE_TEST,<Unused>,TEST_CLAUSE,"TEST @Value(type) = Native Application",Native Applications,BOOL_OP,OR,COMPOSITE_TEST,<Unused>,TEST_CLAUSE,"TEST @Value(type) = Native Application Template",Native Application Templates,BOOL_OP,OR,COMPOSITE_TEST,<Unused>,TEST_CLAUSE,"TEST @Value(type) = Native Application Installer",Native App Installers,BOOL_OP,OR,COMPOSITE_TEST,<Unused>,TEST_CLAUSE,"TEST @Value(type) = Geometry Service",Geometry Services,BOOL_OP,OR,COMPOSITE_TEST,<Unused>,TEST_CLAUSE,"TEST @Value(type) = Geocoding Service",Geocoding Services,BOOL_OP,OR,COMPOSITE_TEST,<Unused>,TEST_CLAUSE,"TEST @Value(type) = Network Analysis Service",Network Analysis Services,BOOL_OP,OR,COMPOSITE_TEST,<Unused>,TEST_CLAUSE,"TEST @Value(type) = Geoprocessing Service",Geoprocessing Services,BOOL_OP,OR,COMPOSITE_TEST,<Unused>,TEST_CLAUSE,"TEST @Value(type) = Workflow Manager Service",Wrokflow Manager Services,BOOL_OP,OR,COMPOSITE_TEST,<Unused>,TEST_CLAUSE,"TEST @Value(type) = Stream Service",Stream Services
    Web Maps -> Check_For_Null_URL_Attribute
    CityEngine Web Scenes -> Check_For_Null_URL_Attribute
    Web Scenes -> Check_For_Null_URL_Attribute
    Pro Maps -> Check_For_Null_URL_Attribute
    Feature Services -> Check_For_Null_URL_Attribute
    Map Services -> Check_For_Null_URL_Attribute
    Image Services -> Check_For_Null_URL_Attribute
    KMLs -> Check_For_Null_URL_Attribute
    WMSs -> Check_For_Null_URL_Attribute
    Feature Collections -> Check_For_Null_URL_Attribute
    Feature Collection Templates -> Check_For_Null_URL_Attribute
    Geodata Services -> Check_For_Null_URL_Attribute
    Globe Services -> Check_For_Null_URL_Attribute
    Web Mapping Applications -> Check_For_Null_URL_Attribute
    Mobile Applications -> Check_For_Null_URL_Attribute
    Code Attachments -> Check_For_Null_URL_Attribute
    Ops Dashboard Add Ins -> Check_For_Null_URL_Attribute
    Operation Views -> Check_For_Null_URL_Attribute
    Ops Dashboard Extensions -> Check_For_Null_URL_Attribute
    Native Applications -> Check_For_Null_URL_Attribute
    Native Application Templates -> Check_For_Null_URL_Attribute
    Native App Installers -> Check_For_Null_URL_Attribute
    Geometry Services -> Check_For_Null_URL_Attribute
    Geocoding Services -> Check_For_Null_URL_Attribute
    Network Analysis Services -> Check_For_Null_URL_Attribute
    Geoprocessing Services -> Check_For_Null_URL_Attribute
    Wrokflow Manager Services -> Check_For_Null_URL_Attribute
    Stream Services -> Check_For_Null_URL_Attribute
Check_For_Null_URL_Attribute: Tester
    TEST_CLAUSE = TEST url NOT_ATTRIBUTE_VALUE_NULL ""
    BOOL_OP = OR
    TEST_MODE = Automatic
    TEST_DESCRIPTION = ""
    PASSED -> FullList
    PASSED -> Edit_URLs_With_URL_Attribute (output)
    FAILED -> Edit_URLs_With_No_URL_Attribute (output)
FullList: Inspector [off]
Edit_URLs_With_URL_Attribute (output)
Edit_URLs_With_No_URL_Attribute (output)
Tester
    TEST_CLAUSE = TEST @Value(type) = Web Map
    BOOL_OP = OR
    TEST_MODE = Automatic
    TEST_DESCRIPTION = ""
    PASSED -> Inspector
Inspector [off]
